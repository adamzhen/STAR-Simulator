import sys
sys.path.append(r"\\storage.it.tamu.edu\TAMU\OAL\Homes\adzheng\Programs\Python\site-packages\python3.10")
import FreeCAD
import otsun
import os
import csv
import math
import time

# start timer
_start_time = time.perf_counter()  # TIMING


# ============================================================================
# Read in Config Parameters
# ============================================================================

# Input config file from Abaqus
config_file = r"H:/STAR-Simulator/FreeCAD/abaqus_to_freecad.txt"

# Initialize parameters
FCSTD_PATH = None
OBJECT_PATH = None
ITER_ID = None
RUN_NO = None
SCENARIO_NAME = None
OBJECT_NAME = None
NUM_RAYS = None
SUN_DIR = None

with open(config_file, 'r') as f:
    for line in f:
        line = line.strip()
        if not line or line.startswith('#'):
            continue
        parts = [p.strip() for p in line.split(',', 1)]
        if len(parts) != 2:
            continue
        key, value = parts
        if key == 'FCSTD_PATH':
            FCSTD_PATH = value
        elif key == 'OBJECT_PATH':
            OBJECT_PATH = value
        elif key == 'ITER_ID':
            ITER_ID = value
        elif key == 'RUN_NO':
            RUN_NO = value
        elif key == 'SCENARIO_NAME':
            SCENARIO_NAME = value
        elif key == 'OBJECT_NAME':
            OBJECT_NAME = value
        elif key == 'NUM_RAYS':
            NUM_RAYS = int(value)
        elif key == 'SUN_DIR':
            # Parse three comma-separated floats
            sun_parts = [p.strip() for p in value.split(',')]
            if len(sun_parts) == 3:
                SUN_DIR = tuple(float(p) for p in sun_parts)
            else:
                raise ValueError("SUN_DIR must have 3 values, got: %s" % value)

# Validation
if FCSTD_PATH is None or OBJECT_PATH is None:
    raise RuntimeError("FCSTD_PATH or OBJECT_PATH not found in %s" % config_file)

if ITER_ID is None:
    raise RuntimeError("ITER_ID not found in %s" % config_file)

if RUN_NO is None:
    raise RuntimeError("RUN_NO not found in %s" % config_file)

if SCENARIO_NAME is None:
    raise RuntimeError("SCENARIO_NAME not found in %s" % config_file)

if OBJECT_NAME is None:
    raise RuntimeError("OBJECT_NAME not found in %s" % config_file)

if NUM_RAYS is None:
    raise RuntimeError("NUM_RAYS not found in %s" % config_file)

if SUN_DIR is None:
    raise RuntimeError("SUN_DIR not found in %s" % config_file)

# Set parameters based on inputs
EXPERIMENT_DATA_FILEPATH = "H:/STAR-Simulator/Scenarios/%s/experiment_data.csv" % SCENARIO_NAME
FLUX_DATA_FILEPATH       = "H:/STAR-Simulator/Scenarios/%s/flux_data.csv" % SCENARIO_NAME
ABSORPTION_PLOT_DIR = "H:/STAR-Simulator/Scenarios/%s/run_documentation/iterative_analysis_%s/plots" % (SCENARIO_NAME, RUN_NO)
os.makedirs(ABSORPTION_PLOT_DIR, exist_ok=True)

PLOT2D = True       # Plot absorption points on 2D graph if PLOT2D is True
DISP3D = False      # Display rays in FreeCAD if True

print("Running with config:")
print("  FCSTD_PATH:", FCSTD_PATH)
print("  OBJECT_PATH:", OBJECT_PATH)
print("  RUN_NO:", RUN_NO)
print("  SCENARIO_NAME:", SCENARIO_NAME)
print("  OBJECT_NAME:", OBJECT_NAME)
print("  NUM_RAYS:", NUM_RAYS)
print("  SUN_DIR:", SUN_DIR)
print("  FLUX_DATA_FILEPATH:", FLUX_DATA_FILEPATH)
print("  ABSORPTION_PLOT_DIR:", ABSORPTION_PLOT_DIR)


# ============================================================================
# HELPER FUNCTIONS
# ============================================================================

def extract_faces_from_solid(doc, solid_obj_label, material_name):
    solid = doc.getObjectsByLabel(solid_obj_label)[0]
    print(f"Extracting {len(solid.Shape.Faces)} faces from '{solid_obj_label}'...")
    
    face_objects = []
    for i, face in enumerate(solid.Shape.Faces):
        face_obj = doc.addObject("Part::Feature", f"{solid.Name}_Face{i}")
        face_obj.Shape = face
        face_obj.Label = f"{solid.Label}_Face{i}"
        face_objects.append(face_obj)
    
    doc.removeObject(solid.Name)
    doc.recompute()
    print(f"Extracted {len(face_objects)} faces")
    return face_objects

def get_tessellation_tolerance(target_faces, ratio=0.002):
    """
    Compute tessellation deflection tolerance as a fraction of the
    bounding box diagonal of the combined target faces.
    ratio=0.002 (0.2%) is the industry standard for silhouette capture.
    """
    import math
    combined_bb = target_faces[0].Shape.BoundBox
    for face_obj in target_faces[1:]:
        combined_bb.add(face_obj.Shape.BoundBox)
    diag = math.sqrt(
        combined_bb.XLength ** 2 +
        combined_bb.YLength ** 2 +
        combined_bb.ZLength ** 2
    )
    return diag * ratio
    
# ============================================================================
# Create Working Copy of FCSTD Document
# ============================================================================

dirpath = os.path.dirname(FCSTD_PATH)
basename, ext = os.path.splitext(os.path.basename(FCSTD_PATH))
counter = 0
while True:
    if counter == 0:
        candidate = f"{basename}_otsun_working{ext}"
    else:
        candidate = f"{basename}_otsun_working_{counter}{ext}"
    temp_path = os.path.join(dirpath, candidate)
    if not os.path.exists(temp_path):
        break
    counter += 1

original_doc = FreeCAD.open(FCSTD_PATH)
original_doc.saveAs(temp_path)
FreeCAD.closeDocument(original_doc.Name)
doc = FreeCAD.open(temp_path)

# --- Clear existing objects in the document ---
for obj in list(doc.Objects):
    doc.removeObject(obj.Name)     # remove everything in the scene
doc.recompute()                    # update document after deletion [web:176]

# ============================================================================
# MAIN SIMULATION SCRIPT
# ============================================================================

# --- Import STEP geometry into this document (console-safe) ---
print("Importing STEP File")
import Import  # non-GUI import module
Import.insert(OBJECT_PATH, doc.Name)  # works in FreeCADCmd
imported_obj = doc.Objects[0]
imported_obj.Label = OBJECT_NAME
doc.recompute()

# --- Extract Faces from Solid ---
print("Extracting Faces")
target_faces = extract_faces_from_solid(doc, OBJECT_NAME, "Aluminum")
print("Done extracting faces")

# --- Define Surface Materials ---
from otsun.materials import SurfaceMaterial

SurfaceMaterial.create("Aluminum", {
    "probability_of_reflection": lambda wl: 0.0,
    "probability_of_absorption": lambda wl: 1.0,
    "probability_of_transmittance": lambda wl: 0.0,
    'thermal_material': True
})
SurfaceMaterial.create("Nitinol", {
    "probability_of_reflection": lambda wl: 0.0,
    "probability_of_absorption": lambda wl: 1.0,
    "probability_of_transmittance": lambda wl: 0.0,
    'thermal_material': True
})
SurfaceMaterial.create("Blocker", {
    "probability_of_reflection":   lambda wl: 0.0,
    "probability_of_absorption":   lambda wl: 1.0,
    "probability_of_transmittance":lambda wl: 0.0,
    "thermal_material":            False,  
})

# --- Build Scene ---
scene = otsun.Scene.from_freecad_document(doc)

print(f"\n=== Scene ===")
print(f"  Faces in scene: {len(scene.faces)}")

## SUN WINDOW ONLY OVER THE TARGET OBJECT
from otsun.source import SunWindow, LightSource
import itertools
from FreeCAD import Base

# Direction of rays from sun window
main_direction = FreeCAD.Base.Vector(*SUN_DIR)

# Create a normal SunWindow first (so we get all methods/attributes)
sun_window = SunWindow(scene, main_direction)

# --- Recompute rectangle using ONLY the target object's faces ---

# Collect bounding boxes of the target faces
bbs = [face_obj.Shape.BoundBox for face_obj in target_faces]

MARGIN = 0.05  # 5% padding on each side to avoid clipping edge rays

projected_points = []
point_of_plane = (scene.boundbox.Center -
                  main_direction * 0.5 * scene.boundbox.DiagonalLength)

for face_obj in target_faces:
    try:
        pts, _ = face_obj.Shape.tessellate(get_tessellation_tolerance(target_faces, ratio=0.002))
        for pt in pts:
            projected_points.append(
                FreeCAD.Base.Vector(pt).projectToPlane(point_of_plane, main_direction)
            )
    except Exception:
        for vertex in face_obj.Shape.Vertexes:
            projected_points.append(
                FreeCAD.Base.Vector(vertex.Point).projectToPlane(point_of_plane, main_direction)
            )

# Cap point count — find_min_rectangle scales poorly above ~1000 pts,
MAX_SUN_WINDOW_POINTS = 800
if len(projected_points) > MAX_SUN_WINDOW_POINTS:
    import random
    # Keep every Nth point (deterministic, preserves spatial distribution)
    step = len(projected_points) // MAX_SUN_WINDOW_POINTS
    projected_points = projected_points[::step]
if not projected_points:
    raise RuntimeError("No projected points found for sun window calculation")

print("Sun window computed from %d tessellation points" % len(projected_points)) 

origin, v1, v2, length1, length2 = SunWindow.find_min_rectangle(
    projected_points, main_direction
)

MARGIN = 0.05  # 5% padding on each side
length1_padded = length1 * (1.0 + 2.0 * MARGIN)
length2_padded = length2 * (1.0 + 2.0 * MARGIN)
origin_padded  = origin - v1 * (length1 * MARGIN) - v2 * (length2 * MARGIN)

sun_window.origin   = origin_padded
sun_window.v1       = v1
sun_window.v2       = v2
sun_window.length1  = length1_padded
sun_window.length2  = length2_padded
sun_window.aperture = length1_padded * length2_padded

print("Sun window size: %.4f m x %.4f m (with %.0f%% margin)" % (
    length1_padded, length2_padded, MARGIN * 100))

# Optional: visualize sun window
sun_window.add_to_document(doc)
doc.recompute()

# --- Define Light Source using this custom SunWindow ---
sun = LightSource(
    scene=scene,
    emitting_region=sun_window,
    light_spectrum=550.0,
    initial_energy=1.0,
    direction_distribution=None,
    polarization_vector=None
)

print(f"\nTIME: {time.perf_counter() - _start_time:.3f} seconds")

# --- Run Experiment ---
num_rays = NUM_RAYS
if DISP3D:
    experiment = otsun.Experiment(
        scene=scene,
        light_source=sun,
        number_of_rays=num_rays,
        document_to_show=doc
    )
else:
    experiment = otsun.Experiment(
        scene=scene,
        light_source=sun,
        number_of_rays=num_rays
    )

print(f"\n=== Running simulation with {num_rays} rays ===")
experiment.run()

print(f"\nTIME: {time.perf_counter() - _start_time:.3f} seconds")

# --- Results ---
print(f"\n=== RESULTS ===")
print(f"Number of absorption points: {len(experiment.points_absorber_Th)}")

SOLAR_IRRADIANCE = 1361.0  # W/m^2
ABSORPTIVITY     = 0.75    # dimensionless surface absorptivity

def absorbed_flux(irradiance, absorptivity, angle_deg):
    """Flux absorbed on a surface for given incidence angle."""
    theta_rad = math.radians(angle_deg)
    return irradiance * absorptivity * math.cos(theta_rad)

with open(EXPERIMENT_DATA_FILEPATH, 'w', newline='') as f_exp, \
     open(FLUX_DATA_FILEPATH, 'w', newline='') as f_flux:

    writer_exp  = csv.writer(f_exp)
    writer_flux = csv.writer(f_flux)

    # Header for full experiment data (+ Flux column added)
    writer_exp.writerow([
        'Energy', 'X', 'Y', 'Z',
        'Normal_X', 'Normal_Y', 'Normal_Z',
        'Wavelength', 'Flux'
    ])

    # Ray direction (unit vector).
    # For SunWindow with direction_distribution=None, rays follow main_direction. [web:34][web:36]
    ray_dir = main_direction.normalize()

    for entry in experiment.points_absorber_Th:
        energy, x1, y1, z1, x2, y2, z2, nx, ny, nz, wavelength = entry

        # Surface normal at hit
        n = FreeCAD.Base.Vector(nx, ny, nz)
        try:
            n = n.normalize()
        except Exception:
            continue  # skip degenerate normals

        # Angle between ray direction and surface normal (0° = normal incidence).
        # If ray travels along main_direction, normal incidence means n == -ray_dir,
        # so cos(theta) = - ray_dir · n. [web:36]
        cos_theta = - (ray_dir.x * n.x + ray_dir.y * n.y + ray_dir.z * n.z)
        cos_theta = max(-1.0, min(1.0, cos_theta))  # clamp
        angle_deg = math.degrees(math.acos(cos_theta))

        flux = absorbed_flux(SOLAR_IRRADIANCE, ABSORPTIVITY, angle_deg)

        # Full data row (including Flux) -> experiment_data.csv
        writer_exp.writerow([
            f"{energy:.6f}",
            f"{x1:.6f}", f"{y1:.6f}", f"{z1:.6f}",
            f"{nx:.6f}", f"{ny:.6f}", f"{nz:.6f}",
            f"{wavelength:.6f}",
            f"{flux:.6f}",
        ])

        # Reduced data row: X, Y, Z, Flux (no header) -> flux_data.csv
        writer_flux.writerow([
            f"{x1:.6f}", f"{y1:.6f}", f"{z1:.6f}", f"{flux:.6f}",
        ])


print(f"\nExperiment data saved: {len(experiment.points_absorber_Th)} points")
print(f"Flux data saved: {len(experiment.points_absorber_Th)} points")


if PLOT2D:
    import os
    import numpy as np
    import matplotlib
    matplotlib.use('Agg')   # non-GUI backend, safe in FreeCADCmd
    import matplotlib.pyplot as plt

    points = getattr(experiment, "points_absorber_Th", None)
    if not points:
        print("No absorption points to plot.")
    else:
        try:
            arr = np.asarray(points, dtype=float)
            xs = arr[:, 1]
            ys = arr[:, 2]
        except Exception:
            xs = [p[1] for p in points if len(p) > 2]
            ys = [p[2] for p in points if len(p) > 2]
            xs = np.array(xs, dtype=float)
            ys = np.array(ys, dtype=float)

        if xs.size == 0:
            print("No valid absorption coordinates found.")
        else:
            plt.figure(figsize=(6, 6))
            plt.scatter(xs, ys, s=0.5, c='k', marker='.')
            plt.xlabel("X")
            plt.ylabel("Y")
            plt.title(f"Absorption points (N={xs.size})")
            plt.gca().set_aspect("equal", adjustable="box")
            plt.tight_layout()

            plot_path = os.path.join(ABSORPTION_PLOT_DIR, f'absorption_plot_{ITER_ID}.png')

            plt.savefig(plot_path, dpi=300, bbox_inches='tight')  # no plt.show() [web:478][web:479]
            plt.close()
            print(f"Plot saved: {plot_path}")


doc.save()
doc.recompute()

# stop timer and report elapsed time
_elapsed = time.perf_counter() - _start_time  # TIMING
print(f"\nTotal script elapsed time: {_elapsed:.3f} seconds")  # TIMING
