import FreeCAD as App
import Part
import Mesh
import Import
import os

RUN_NO = 0.63
SCENARIO_NAME = "SMAScenario1"

# Path to your scenario file and geometry folder
DOC_NAME = "SMAScenario1_Sequence%s" % RUN_NO
DOCUMENTATION_DIR = "H:/STAR-Simulator/Scenarios/%s/run_documentation/iterative_analysis_%s" % (SCENARIO_NAME, RUN_NO)
IMPORT_OBJECT_FILEPATH = f"H:/STAR-Simulator/Scenarios/{SCENARIO_NAME}/SMAStrip (Nitinol).stp"
FCSTD_PATH = "%s/%s.FCStd" % (DOCUMENTATION_DIR, DOC_NAME)
GEOMETRY_DIR = "%s/deformed_cad" % DOCUMENTATION_DIR

# Open existing scenario, or create new
if os.path.exists(FCSTD_PATH):
    doc = App.open(FCSTD_PATH)
else:
    doc = App.newDocument(DOC_NAME)

# Get all STEP files
step_files = sorted(f for f in os.listdir(GEOMETRY_DIR)
                    if f.lower().endswith((".stp", ".step")))

# Get all OBJ files
obj_files = sorted(f for f in os.listdir(GEOMETRY_DIR)
                   if f.lower().endswith(".obj"))

# Import STEP files
for fname in step_files:
    path = os.path.join(GEOMETRY_DIR, fname)
    base, _ = os.path.splitext(fname)
    print("Importing STEP:", path)

    shape = Part.Shape()
    shape.read(path)
    obj = doc.addObject("Part::Feature", base)
    obj.Shape = shape

# Import OBJ files (mesh format)
for fname in obj_files:
    path = os.path.join(GEOMETRY_DIR, fname)
    base, _ = os.path.splitext(fname)
    print("Importing OBJ:", path)

    mesh = Mesh.Mesh(path)
    obj = doc.addObject("Mesh::Feature", base)
    obj.Mesh = mesh

# Import the fixed SMA strip STEP file
if os.path.exists(IMPORT_OBJECT_FILEPATH):
    import_base = os.path.splitext(os.path.basename(IMPORT_OBJECT_FILEPATH))[0]
    print("Importing fixed STEP:", IMPORT_OBJECT_FILEPATH)

    # Remove existing object with same label/name to avoid duplicates on rerun
    for existing in list(doc.Objects):
        if existing.Label == import_base or existing.Name == import_base:
            doc.removeObject(existing.Name)

    shape = Part.Shape()
    shape.read(IMPORT_OBJECT_FILEPATH)
    sma_obj = doc.addObject("Part::Feature", import_base)
    sma_obj.Label = import_base
    sma_obj.Shape = shape
else:
    print("Fixed STEP file not found:", IMPORT_OBJECT_FILEPATH)

doc.recompute()
doc.saveAs(FCSTD_PATH)
print("Imported %d STEP files, %d OBJ files, and fixed SMA strip into %s" %
      (len(step_files), len(obj_files), FCSTD_PATH))
