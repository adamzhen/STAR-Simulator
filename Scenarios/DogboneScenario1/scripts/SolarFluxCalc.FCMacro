##### SolarFluxCalc.FCMacro #####
##### Version 1.1           #####

# ============================================================================
# IMPORT LIBRARIES
# ============================================================================

import os
import sys
import FreeCAD
import Part
import csv
import math
import json
import time
import numpy as np

sys.path.append(r"\\storage.it.tamu.edu\TAMU\OAL\Homes\adzheng\Programs\Python\site-packages\python3.10")
import otsun
import otsun.source
from otsun.ray import Ray, _ray_may_intersect_bb, _bb_intersects, part_line

# start timer
_start_time = time.perf_counter()  # TIMING

# ============================================================================
# Read in Parameters
# ============================================================================

try:
	script_dir = os.path.dirname(os.path.abspath(__file__))
except NameError: # Change this manually to the correct directory if os.path fails
	script_dir = r"C:\Users\adzheng\STAR-Simulator\Scenarios\SMAScenario1\scripts"
	print("WARNING: Script directory path detection failed. Manual directory setting used.")

config_file = os.path.normpath(os.path.join(script_dir, "..", "abaqus_to_freecad.json"))
if not os.path.isfile(config_file):
	raise FileNotFoundError(f"Config file not found at: {config_file}")

REQUIRED_KEYS = ['WORKING_DIR', 'FCSTD_PATH', 'OBJECT_PATH', 'OBJECT_NAME', 'OBJECT_TYPE',
                 'ITER_ID', 'RUN_NO', 'SCENARIO_NAME', 'NUM_RAYS', 'SUN_DIR',
                 'SOLAR_IRRADIANCE', 'OBJECT_MATERIAL', 'ABSORPTION_ONLY', 'ABSORPTIVITY_DICT', 'GEOMETRY_IMPORT']

with open(config_file, 'r') as f:
    cfg = json.load(f)

missing = [k for k in REQUIRED_KEYS if k not in cfg]
if missing:
    raise RuntimeError(f"Missing required keys {missing} in {config_file}")

cfg['SUN_DIR'] = tuple(cfg['SUN_DIR'])

WORKING_DIR = cfg['WORKING_DIR']
FCSTD_PATH = cfg['FCSTD_PATH']
OBJECT_PATH = cfg['OBJECT_PATH']
OBJECT_NAME = cfg['OBJECT_NAME']
ITER_ID = cfg['ITER_ID']
RUN_NO = cfg['RUN_NO']
SCENARIO_NAME = cfg['SCENARIO_NAME']
NUM_RAYS = cfg['NUM_RAYS']
SUN_DIR = cfg['SUN_DIR']
SOLAR_IRRADIANCE = cfg['SOLAR_IRRADIANCE']
OBJECT_MATERIAL = cfg['OBJECT_MATERIAL']
ABSORPTION_ONLY = cfg['ABSORPTION_ONLY']
ABSORPTIVITY_DICT = cfg['ABSORPTIVITY_DICT']
OBJECT_TYPE = cfg.get('OBJECT_TYPE')          # 'shell' or 'wire'
GEOMETRY_IMPORT = cfg.get('GEOMETRY_IMPORT')     # 'stp' or 'nodes'
NODE_DATA = cfg.get('NODE_DATA', None)
RAY_ENGINE = cfg.get('RAY_ENGINE', 'FastRay')  # 'FastRay' (default) or 'Ray' (stock OTSun)
RANDOM_SEED = cfg.get('RANDOM_SEED', None)     # optional int: reproducible ray sampling
GEOMETRY_EXPORT_PATH = cfg.get('GEOMETRY_EXPORT_PATH', None)  # optional: save ray-traced target geometry (STEP) here

# ============================================================================
# Set Parameters
# ============================================================================

EXPERIMENT_DATA_FILEPATH = f"{WORKING_DIR}/experiment_data.csv"
FLUX_DATA_FILEPATH = f"{WORKING_DIR}/flux_data.csv"
DOCUMENTATION_DIR = f"{WORKING_DIR}/run_documentation/run_{RUN_NO}"
ABSORPTION_PLOT_DIR = f"{DOCUMENTATION_DIR}/plots"
os.makedirs(ABSORPTION_PLOT_DIR, exist_ok=True)

PLOT2D = True # Plot absorption points on 2D graph if PLOT2D is True
DISP3D = False # Display rays in FreeCAD if True
KEEP_WORKING_COPY = True # Keeps working copy of .Fcstd doc used for ray tracing

OBJECT_ABSORPTIVITY = ABSORPTIVITY_DICT[OBJECT_MATERIAL]

print("Running with config:")
for key in REQUIRED_KEYS:
	print(f" {key}:", cfg[key])
print(" RAY_ENGINE:", RAY_ENGINE)
print(" FLUX_DATA_FILEPATH:", FLUX_DATA_FILEPATH)
print(" ABSORPTION_PLOT_DIR:", ABSORPTION_PLOT_DIR)



### Set Output Path for FreeCAD -> Abaqus Data Transfer ###
FREECAD_TO_ABAQUS_JSON = os.path.normpath(os.path.join(script_dir, "..", "freecad_to_abaqus.json"))

# ============================================================================
# FASTRAY: accelerated OTSun Ray (same results as stock otsun.ray.Ray)
# ============================================================================
# Stock Ray.next_intersection loops over every scene face in Python, reading
# face.BoundBox and running two box checks per face, every ray step. FastRay
# caches all face bounding boxes once per scene as numpy arrays and does one
# vectorised ray-box (slab) test to pick the few faces the ray can reach. Only
# those go through OTSun's own checks and face.section(), in the original face
# order, so hits are identical. Everything else (materials, reflection,
# absorption, Experiment) is stock OTSun.
# Verified identical to stock Ray on OTSun 2.14.0 (tests/otsun_geometry/).
# Assumes the scene's faces do not change after the first ray is traced.

FASTRAY_VERIFIED_OTSUN_VERSIONS = ("2.14.0",)


def _otsun_version():
    try:
        from importlib.metadata import version
        return version("otsun")
    except Exception:
        return getattr(otsun, "__version__", "unknown")


def _fastray_scene_cache(scene):
    cache = getattr(scene, "_fastray_cache", None)
    if cache is not None:
        return cache
    bbs = [f.BoundBox for f in scene.faces]
    lo = np.array([[b.XMin, b.YMin, b.ZMin] for b in bbs])
    hi = np.array([[b.XMax, b.YMax, b.ZMax] for b in bbs])
    tol = max([f.getTolerance(1) for f in scene.faces] + [0.0])
    pad = 2.0 * max(tol, scene.epsilon)       # conservative inflation
    cache = {"bbs": bbs, "lo": lo - pad, "hi": hi + pad}
    scene._fastray_cache = cache
    return cache


def _slab_candidates(lo, hi, o, d, tmax):
    """Indices (ascending) of boxes crossed by the segment o + t*d, t in [0, tmax]. Used to find faces that a ray can reach."""
    t0 = np.zeros(len(lo))
    t1 = np.full(len(lo), tmax)
    keep = np.ones(len(lo), bool)
    for k in range(3):
        if d[k] == 0.0:
            keep &= (o[k] >= lo[:, k]) & (o[k] <= hi[:, k])
        else:
            a = (lo[:, k] - o[k]) / d[k]
            b = (hi[:, k] - o[k]) / d[k]
            t0 = np.maximum(t0, np.minimum(a, b))
            t1 = np.minimum(t1, np.maximum(a, b))
    keep &= t0 <= t1
    return np.nonzero(keep)[0]


class FastRay(Ray):
    """otsun.ray.Ray with a vectorised bounding-box prefilter in next_intersection.
    The loop body below is copied from OTSun 2.14.0's Ray.next_intersection."""

    def next_intersection(self):
        scene = self.scene
        cache = _fastray_scene_cache(scene)
        max_distance = 5 * scene.diameter
        p0 = self.points[-1]
        direction = self.current_direction()
        intersections = []
        p1 = p0 + direction * max_distance
        shape_segment = part_line(p0, p1).toShape()
        bb1 = shape_segment.BoundBox
        o = np.array([p0.x, p0.y, p0.z])
        d = np.array([direction.x, direction.y, direction.z])
        for i in _slab_candidates(cache["lo"], cache["hi"], o, d, max_distance):
            face = scene.faces[i]
            bb2 = cache["bbs"][i]
            if not _ray_may_intersect_bb(bb2, p0, direction):
                continue
            if not _bb_intersects(bb1, bb2):
                continue
            punts = face.section(shape_segment).Vertexes
            if not punts:
                continue
            if (id(face) in scene.materials) & (face != self.last_touched_face):
                for punt in punts:
                    intersections.append([punt.Point, face])
            else:
                for punt in punts:
                    if p0.distanceToPoint(punt.Point) > scene.epsilon:
                        intersections.append([punt.Point, face])
        if not intersections:
            return p1, None
        closest_pair = min(intersections, key=lambda pair: self.weighted_distance(p0, pair))
        return tuple(closest_pair)


def select_ray_engine(requested):
    """Install the requested Ray class in otsun.source (where LightSource
    creates rays). Falls back to stock Ray if FastRay has not been verified
    against the installed OTSun version. Returns the engine name in use."""
    otsun.source.Ray = Ray
    if requested == 'Ray':
        print("Ray engine: stock otsun Ray")
        return 'Ray'
    if requested != 'FastRay':
        raise ValueError(f"Unknown RAY_ENGINE: {requested!r}. Must be 'FastRay' or 'Ray'.")
    ver = _otsun_version()
    if ver not in FASTRAY_VERIFIED_OTSUN_VERSIONS:
        print(f"WARNING: FastRay was verified only on OTSun {FASTRAY_VERIFIED_OTSUN_VERSIONS}, "
              f"found {ver}. Falling back to stock otsun Ray (slower, always correct).")
        return 'Ray'
    otsun.source.Ray = FastRay
    print(f"Ray engine: FastRay (OTSun {ver})")
    return 'FastRay'


def triangulate_elements(nodes, elements):
    """Safety net: split any 4-node element along its shorter diagonal.
    Triangles pass through. starlib.triangulate_shell_elements normally
    does this on the Abaqus side already."""
    tris = []
    for elem in elements:
        if len(elem) == 3:
            tris.append(tuple(elem))
        elif len(elem) == 4:
            a, b, c, d = elem
            if (nodes[a] - nodes[c]).Length <= (nodes[b] - nodes[d]).Length:
                tris += [(a, b, c), (a, c, d)]
            else:
                tris += [(a, b, d), (b, c, d)]
        else:
            raise ValueError(f"Shell element with {len(elem)} nodes is not supported: {elem}")
    return tris


# ============================================================================
# HELPER FUNCTIONS
# ============================================================================

def build_wire_pipefuse(nodes, elements, radius=0.02):
    """
    Build individual swept-pipe solids for straight truss segments and fuse them.

    nodes: dict {node_id: App.Vector(x, y, z)}
    elements: list of (node1_id, node2_id) tuples
    radius: cross-section radius (m), from Abaqus Property module
    """
    solids = []
    for n1, n2 in elements:
        p1, p2 = nodes[n1], nodes[n2]
        direction = p2.sub(p1)
        if direction.Length < 1e-9:
            continue

        edge = Part.LineSegment(p1, p2).toShape()
        path = Part.Wire([edge])

        circle = Part.Circle(p1, direction, radius)
        profile = Part.Wire([circle.toShape()])

        pipe = path.makePipeShell([profile], True, True)
        solids.append(pipe)

    if not solids:
        raise ValueError("No valid elements to build geometry from.")

    fused = solids[0].fuse(solids[1:]) if len(solids) > 1 else solids[0]
    return fused


def remove_existing_target(doc, object_name):
    """
    Remove only a previous instance of the target object (by label),
    leaving every other object in the scene untouched.
    """
    existing = doc.getObjectsByLabel(object_name)
    for obj in existing:
        doc.removeObject(obj.Name)
    if existing:
        doc.recompute()
        print(f"Removed {len(existing)} pre-existing object(s) labeled '{object_name}'")


def import_target_from_stp(doc, object_path, object_name):
    """Import target geometry from a STEP file (console-safe)."""
    import Import  # non-GUI import module
    n_before = len(doc.Objects)
    Import.insert(object_path, doc.Name)  # works in FreeCADCmd
    new_objs = doc.Objects[n_before:]
    if not new_objs:
        raise RuntimeError(f"STEP import produced no new objects from {object_path}")
    imported_obj = new_objs[0]
    imported_obj.Label = object_name
    doc.recompute()
    return imported_obj


def build_target_from_nodes(doc, object_type, node_data, object_name):
    """
    Reconstruct target geometry in FreeCAD directly from Abaqus node/element
    data, without importing a STEP file. Supports 'wire' (swept-pipe truss)
    and 'shell' (flat/faceted plate from node coordinates) object types.
    """
    if node_data is None:
        raise ValueError("GEOMETRY_IMPORT is 'nodes' but NODE_DATA was not provided.")

    raw_nodes = node_data['nodes']
    nodes = {int(nid): FreeCAD.Vector(*coords) for nid, coords in raw_nodes.items()}
    elements = [tuple(e) for e in node_data['elements']]

    if object_type == 'wire':
        radius = node_data.get('radius', 0.02)
        shape = build_wire_pipefuse(nodes, elements, radius=radius)

    elif object_type == 'shell':
        # One flat triangular face per element ("G1" in tests/otsun_geometry).
        # Quads are split into triangles: a slightly twisted quad cannot be
        # made into a planar Part.Face.
        tris = triangulate_elements(nodes, elements)
        faces = []
        n_degenerate = 0
        for a, b, c in tris:
            pa, pb, pc = nodes[a], nodes[b], nodes[c]
            if (pb - pa).cross(pc - pa).Length < 1e-18:   # zero-area triangle
                n_degenerate += 1
                continue
            faces.append(Part.Face(Part.makePolygon([pa, pb, pc, pa])))
        if not faces:
            raise ValueError("No valid shell triangles in NODE_DATA.")
        if n_degenerate:
            print(f"WARNING: skipped {n_degenerate} zero-area triangles")
        print(f"Built {len(faces)} triangular faces from {len(elements)} elements")
        # Compound (not Shell): faces are split into separate objects below anyway
        shape = Part.makeCompound(faces) if len(faces) > 1 else faces[0]

    else:
        raise ValueError(f"Unknown OBJECT_TYPE: {object_type!r}. Must be 'shell' or 'wire'.")

    target_obj = doc.addObject("Part::Feature", object_name)
    target_obj.Shape = shape
    target_obj.Label = object_name
    doc.recompute()
    return target_obj
    
def extract_faces_from_solid(doc, solid_obj_label):
	solid = doc.getObjectsByLabel(solid_obj_label)[0]
	print(f"Extracting {len(solid.Shape.Faces)} faces from '{solid_obj_label}'...")
	
	face_objects = []
	for i, face in enumerate(solid.Shape.Faces):
		face_obj = doc.addObject("Part::Feature", f"{solid.Name}_Face{i}")
		face_obj.Shape = face
		face_obj.Label = f"{solid.Label}_Face{i}"
		face_objects.append(face_obj)
	
	doc.removeObject(solid.Name)
	doc.recompute()
	print(f"Extracted {len(face_objects)} faces")
	return face_objects


def compute_geometry_complexity(target_faces, verbose=True):
    """Score each face by analytical surface/curve type to estimate
    ray-intersection cost. Closed-form surfaces (plane, cylinder, cone,
    sphere, torus) are cheap; Bezier/B-spline surfaces require iterative
    root-finding per ray and are much more expensive. Trimming curve
    type on each edge adds secondary cost since OCC must also evaluate
    the 2D trimming boundary during intersection.

    Returns dict with per-face breakdown and aggregate scores.
    """
    import Part

    SURFACE_WEIGHTS = {
        'Plane': 1.0,
        'Cylinder': 2.5,
        'Cone': 3.0,
        'Sphere': 3.0,
        'Toroid': 4.0,
        'SurfaceOfRevolution': 8.0,
        'SurfaceOfExtrusion': 8.0,
        'OffsetSurface': 10.0,
        'BezierSurface': 20.0,
        'BSplineSurface': 40.0,
    }
    CURVE_WEIGHTS = {
        'Line': 1.0,
        'Circle': 1.5,
        'Ellipse': 2.0,
        'Parabola': 2.0,
        'Hyperbola': 2.0,
        'BezierCurve': 5.0,
        'BSplineCurve': 8.0,
        'OffsetCurve': 8.0,
    }

    per_face = []
    surf_type_counts = {}
    curve_type_counts = {}
    total_score = 0.0

    for face_obj in target_faces:
        for face in face_obj.Shape.Faces:
            surf = face.Surface
            surf_type = type(surf).__name__
            surf_type_counts[surf_type] = surf_type_counts.get(surf_type, 0) + 1
            base_weight = SURFACE_WEIGHTS.get(surf_type, 15.0)  # unknown -> assume moderately costly

            pole_factor = 1.0
            degree_info = ''
            if surf_type == 'BSplineSurface':
                try:
                    nu = surf.NbUPoles
                    nv = surf.NbVPoles
                    du = surf.UDegree
                    dv = surf.VDegree
                    pole_factor = 1.0 + 0.02 * (nu * nv)
                    degree_info = 'deg=(%d,%d) poles=(%d,%d)' % (du, dv, nu, nv)
                except Exception:
                    pass

            edge_score = 0.0
            edge_count = 0
            for edge in face.Edges:
                curve_type = type(edge.Curve).__name__
                curve_type_counts[curve_type] = curve_type_counts.get(curve_type, 0) + 1
                edge_score += CURVE_WEIGHTS.get(curve_type, 6.0)
                edge_count += 1
            edge_score_avg = edge_score / edge_count if edge_count else 0.0

            face_score = base_weight * pole_factor + edge_score_avg
            total_score += face_score

            per_face.append({
                'label': face_obj.Label,
                'surface_type': surf_type,
                'degree_info': degree_info,
                'num_edges': edge_count,
                'area': face.Area,
                'score': face_score,
            })

    result = {
        'num_faces': len(per_face),
        'total_complexity_score': total_score,
        'mean_complexity_per_face': total_score / len(per_face) if per_face else 0.0,
        'surface_type_counts': surf_type_counts,
        'curve_type_counts': curve_type_counts,
        'per_face': per_face,
    }

    if verbose:
        print("\n=== Geometry Complexity Report ===")
        print("Total faces: %d" % result['num_faces'])
        print("Surface type breakdown:")
        for stype, count in sorted(surf_type_counts.items(), key=lambda x: -x[1]):
            print("  %-22s %d" % (stype, count))
        print("Edge curve type breakdown:")
        for ctype, count in sorted(curve_type_counts.items(), key=lambda x: -x[1]):
            print("  %-22s %d" % (ctype, count))
        print("Total complexity score: %.2f" % result['total_complexity_score'])
        print("Mean complexity/face:   %.2f" % result['mean_complexity_per_face'])
        top5 = sorted(per_face, key=lambda f: -f['score'])[:5]
        print("Top 5 most complex faces:")
        for f in top5:
            print("  %-30s %-16s score=%.2f  %s" %
                  (f['label'], f['surface_type'], f['score'], f['degree_info']))
        print("===================================\n")

    return result
    
    
def absorbed_flux(irradiance, absorptivity, angle_deg):
	"""Flux absorbed on a surface for given incidence angle."""
	theta_rad = math.radians(angle_deg)
	return irradiance * absorptivity * math.cos(theta_rad)

def get_tessellation_tolerance(target_faces, ratio=0.002):
	"""
	Compute tessellation deflection tolerance as a fraction of the
	bounding box diagonal of the combined target faces.
	ratio=0.002 (0.2%) is the industry standard for silhouette capture.
	"""
	import math
	combined_bb = target_faces[0].Shape.BoundBox
	for face_obj in target_faces[1:]:
		combined_bb.add(face_obj.Shape.BoundBox)
	diag = math.sqrt(
		combined_bb.XLength ** 2 +
		combined_bb.YLength ** 2 +
		combined_bb.ZLength ** 2
	)
	return diag * ratio
	
def write_result_json(success, num_faces=None, flux_data_path=None, error_message=None):
	result = {
		"SUCCESS": success,
		"NUM_FACES": num_faces,
		"FLUX_DATA_PATH": flux_data_path,
		"ERROR_MESSAGE": error_message,
		"RAY_ENGINE": ray_engine_used,
		"RAY_TRACE_SECONDS": ray_trace_seconds,
	}
	with open(FREECAD_TO_ABAQUS_JSON, 'w') as f:
		json.dump(result, f, indent=2)
	print(f"Wrote FreeCAD result file: {FREECAD_TO_ABAQUS_JSON}")


# ============================================================================
# MAIN SIMULATION SCRIPT
# ============================================================================

success = False
num_faces = None
error_message = None
ray_engine_used = None
ray_trace_seconds = None

try:

    # ----------------------------------------------------------
    # Set Up FCSTD Document
    # ----------------------------------------------------------
    
    # --- Create working copy of the FCSTD document (unchanged) ---
    dirpath = os.path.dirname(FCSTD_PATH)
    basename, ext = os.path.splitext(os.path.basename(FCSTD_PATH))
    counter = 0
    print("Im here")
    while True:
        if counter == 0:
            candidate = f"{basename}_otsun_working{ext}"
        else:
            candidate = f"{basename}_otsun_working_{counter}{ext}"
        temp_path = os.path.join(dirpath, candidate)
        if not os.path.exists(temp_path):
            break
        counter += 1
    
    original_doc = FreeCAD.open(FCSTD_PATH)
    original_doc.saveAs(temp_path)
    FreeCAD.closeDocument(original_doc.Name)
    doc = FreeCAD.open(temp_path)
    
    # --- Remove only a stale copy of the target object, keep everything else ---
    remove_existing_target(doc, OBJECT_NAME)
    
    # --- Import or reconstruct target geometry, depending on config ---
    if GEOMETRY_IMPORT == 'stp':
        print("Importing STEP File")
        imported_obj = import_target_from_stp(doc, OBJECT_PATH, OBJECT_NAME)
    
    elif GEOMETRY_IMPORT == 'nodes':
        print(f"Reconstructing '{OBJECT_TYPE}' geometry from node data")
        imported_obj = build_target_from_nodes(doc, OBJECT_TYPE, NODE_DATA, OBJECT_NAME)
    
    else:
        raise ValueError(f"Unknown GEOMETRY_IMPORT: {GEOMETRY_IMPORT!r}. Must be 'stp' or 'nodes'.")
    
    doc.recompute()
    
    # --- Extract Faces from Solid/Shell ---
    print("Extracting Faces")
    target_faces = extract_faces_from_solid(doc, OBJECT_NAME)
    print("Done extracting faces")
    
    # Evaluate complexity of geometry in the FCSTD document
    geometry_complexity = compute_geometry_complexity(target_faces)
    
    # --- Save the exact target geometry used for ray tracing (debug; non-fatal) ---
    if GEOMETRY_EXPORT_PATH:
        try:
            os.makedirs(os.path.dirname(GEOMETRY_EXPORT_PATH), exist_ok=True)
            Part.makeCompound([fo.Shape for fo in target_faces]).exportStep(GEOMETRY_EXPORT_PATH)
            print(f"Saved ray-traced target geometry ({len(target_faces)} faces): {GEOMETRY_EXPORT_PATH}")
        except Exception as _e:
            print(f"WARNING: could not save ray-traced geometry to {GEOMETRY_EXPORT_PATH}: {_e}")
    
    # ----------------------------------------------------------
    # Define Surface Materials
    # ----------------------------------------------------------
    
    from otsun.materials import SurfaceMaterial
    
    if ABSORPTION_ONLY:
    	for material_name, absorptivity in ABSORPTIVITY_DICT.items():
    		SurfaceMaterial.create(material_name, {
    			"probability_of_reflection": lambda wl: 0.0,
    			"probability_of_absorption": lambda wl: 1.0,
    			"probability_of_transmittance": lambda wl: 0.0,
    			'thermal_material': material_name != "Blocker",
    		})
    else:
    	raise NotImplementedError(
    		"Please set ABSORPTION_ONLY=True. ABSORPTION_ONLY=False has not yet been implemented."
    	)
    print(f"Created {len(ABSORPTIVITY_DICT)} surface materials (ABSORPTION_ONLY={ABSORPTION_ONLY}): {', '.join(ABSORPTIVITY_DICT.keys())}")
    
    # ----------------------------------------------------------
    # Build OTSun Scene
    # ----------------------------------------------------------
       
    scene = otsun.Scene.from_freecad_document(doc)
    
    print(f"\n=== Scene ===")
    num_faces = len(scene.faces)
    print(f"  Faces in scene: {num_faces}")
    
    # ----------------------------------------------------------
    # Create Sun Window & Define LightSource
    # ----------------------------------------------------------
    
    ## SUN WINDOW ONLY OVER THE TARGET OBJECT
    from otsun.source import SunWindow, LightSource
    import itertools
    from FreeCAD import Base
    
    # Direction of rays from sun window
    main_direction = FreeCAD.Base.Vector(*SUN_DIR)
    
    # Create a SunWindow object WITHOUT running SunWindow.__init__: the
    # constructor fits a rectangle to 8 bounding-box corners of EVERY scene
    # face with an O(n^3) search, which never finishes for a 1000+ face
    # triangle mesh (~12k points). All attributes are set below.
    sun_window = SunWindow.__new__(SunWindow)
    sun_window.main_direction = main_direction
    
    # --- Recompute rectangle using ONLY the target object's faces ---
    
    # Collect bounding boxes of the target faces
    bbs = [face_obj.Shape.BoundBox for face_obj in target_faces]
    
    MARGIN = 0.05  # 5% padding on each side to avoid clipping edge rays
    
    projected_points = []
    point_of_plane = (scene.boundbox.Center -
    				main_direction * 0.5 * scene.boundbox.DiagonalLength)
    
    # Computed once: it loops over all target faces, so calling it per face is O(n^2)
    tess_tol = get_tessellation_tolerance(target_faces, ratio=0.002)
    for face_obj in target_faces:
    	try:
    		pts, _ = face_obj.Shape.tessellate(tess_tol)
    		for pt in pts:
    			projected_points.append(
    				FreeCAD.Base.Vector(pt).projectToPlane(point_of_plane, main_direction)
    			)
    	except Exception:
    		for vertex in face_obj.Shape.Vertexes:
    			projected_points.append(
    				FreeCAD.Base.Vector(vertex.Point).projectToPlane(point_of_plane, main_direction)
    			)
    
    if not projected_points:
    	raise RuntimeError("No projected points found for sun window calculation")

    # find_min_rectangle is O(n^3) in the number of points. The minimum
    # enclosing rectangle depends only on the convex hull, so pass just the
    # hull vertices (same rectangle as using all points, far fewer points).
    n_projected = len(projected_points)
    try:
    	from scipy.spatial import ConvexHull
    	_d = FreeCAD.Base.Vector(main_direction); _d.normalize()
    	_a = FreeCAD.Base.Vector(1, 0, 0) if abs(_d.x) < 0.9 else FreeCAD.Base.Vector(0, 1, 0)
    	_e1 = _d.cross(_a); _e1.normalize()
    	_e2 = _d.cross(_e1)
    	_uv = np.array([[p.dot(_e1), p.dot(_e2)] for p in projected_points])
    	projected_points = [projected_points[i] for i in ConvexHull(_uv).vertices]
    except Exception as _e:
    	print(f"WARNING: convex hull failed ({_e}); subsampling projected points instead")
    	MAX_SUN_WINDOW_POINTS = 800
    	if len(projected_points) > MAX_SUN_WINDOW_POINTS:
    		step = len(projected_points) // MAX_SUN_WINDOW_POINTS
    		projected_points = projected_points[::step]

    print("Sun window computed from %d hull points (of %d projected tessellation points)"
          % (len(projected_points), n_projected))
    
    origin, v1, v2, length1, length2 = SunWindow.find_min_rectangle(
    	projected_points, main_direction
    )

    # --- Force window normal to align with ray direction ---
    normal = v1.cross(v2)
    if normal.dot(main_direction) < 0:
        origin = origin + v2 * length2   # move to opposite corner FIRST
        v2 = v2 * -1                      # then flip
        print("Flipped v2 and shifted origin to correct handedness")

    MARGIN = 0.08  # Padding on each side of sun window
    length1_padded = length1 * (1.0 + 2.0 * MARGIN)
    length2_padded = length2 * (1.0 + 2.0 * MARGIN)
    origin_padded  = origin - v1 * (length1 * MARGIN) - v2 * (length2 * MARGIN)
    
    sun_window.origin   = origin_padded
    sun_window.v1       = v1
    sun_window.v2       = v2
    sun_window.length1  = length1_padded
    sun_window.length2  = length2_padded
    sun_window.aperture = length1_padded * length2_padded
        
    # Summarise target face normals vs sun direction (one line, not one per face).
    # Face orientation does not affect OTSun hits (intersections are two-sided);
    # the flux CSV uses |cos| of the hit normal.
    _dots = []
    for face_obj in target_faces:
        face = face_obj.Shape.Faces[0]
        u_mid = (face.ParameterRange[0] + face.ParameterRange[1]) / 2
        v_mid = (face.ParameterRange[2] + face.ParameterRange[3]) / 2
        _dots.append(face.normalAt(u_mid, v_mid).dot(main_direction * -1))
    print("Target face normals: %d faces, %d facing the sun, normal·(-sun_dir) min %.3f / max %.3f"
          % (len(_dots), sum(1 for x in _dots if x > 0), min(_dots), max(_dots)))
    
    print("Sun window size: %.4f m x %.4f m (with %.0f%% margin)" % (
    	length1_padded, length2_padded, MARGIN * 100))
    
    # Optional: visualize sun window
    sun_window.add_to_document(doc)
    doc.recompute()
    
    # --- Define Light Source using this custom SunWindow ---
    sun = LightSource(
    	scene=scene,
    	emitting_region=sun_window,
    	light_spectrum=550.0,
    	initial_energy=1.0,
    	direction_distribution=None,
    	polarization_vector=None
    )
    
    print(f"\nTIME: {time.perf_counter() - _start_time:.3f} seconds")
    
    # ----------------------------------------------------------
    # Run Experiment
    # ----------------------------------------------------------
    # (Removed: auto-flip of target faces. It ran after the OTSun scene was
    # built, so the scene never saw the flipped faces; it had no effect.)

    # --- Select ray engine (FastRay default, stock Ray optional) ---
    ray_engine_used = select_ray_engine(RAY_ENGINE)

    num_rays = NUM_RAYS
    if DISP3D:
    	experiment = otsun.Experiment(
    		scene=scene,
    		light_source=sun,
    		number_of_rays=num_rays,
    		document_to_show=doc
    	)
    else:
    	experiment = otsun.Experiment(
    		scene=scene,
    		light_source=sun,
    		number_of_rays=num_rays
    	)
    
    print(f"\n=== Running simulation with {num_rays} rays ({ray_engine_used}) ===")
    if RANDOM_SEED is not None:
        # OTSun samples ray origins with random.random and np.random
        import random
        random.seed(RANDOM_SEED)
        np.random.seed(RANDOM_SEED)
        print(f"Random seed: {RANDOM_SEED}")
    _ray_t0 = time.perf_counter()
    experiment.run()
    ray_trace_seconds = time.perf_counter() - _ray_t0
    print(f"Ray tracing: {ray_trace_seconds:.2f} s ({1e3 * ray_trace_seconds / max(num_rays, 1):.3f} ms/ray)")
    
    print(f"\nTIME: {time.perf_counter() - _start_time:.3f} seconds")
    
    if not hasattr(experiment, "points_absorber_Th") or len(experiment.points_absorber_Th) == 0:
    	raise RuntimeError("Ray tracing completed but produced zero absorption points")
    
    doc.save()
    doc.recompute()
    
    success = True
    
    # ----------------------------------------------------------
    # Print and Output Results
    # ----------------------------------------------------------
    
    print(f"\n=== RESULTS ===")
    print(f"Number of absorption points: {len(experiment.points_absorber_Th)}")
    
    with open(EXPERIMENT_DATA_FILEPATH, 'w', newline='') as f_exp, \
    		open(FLUX_DATA_FILEPATH, 'w', newline='') as f_flux:
    
    	writer_exp  = csv.writer(f_exp)
    	writer_flux = csv.writer(f_flux)
    
    	# Header for full experiment data (+ Flux column added)
    	writer_exp.writerow([
    		'Energy', 'X', 'Y', 'Z',
    		'Normal_X', 'Normal_Y', 'Normal_Z',
    		'Wavelength', 'Flux'
    	])
    
    	# Ray direction (unit vector).
    	# For SunWindow with direction_distribution=None, rays follow main_direction. [web:34][web:36]
    	ray_dir = main_direction.normalize()
    
    	for entry in experiment.points_absorber_Th:
    		energy, x1, y1, z1, x2, y2, z2, nx, ny, nz, wavelength = entry
    
    		# Surface normal at hit
    		n = FreeCAD.Base.Vector(nx, ny, nz)
    		try:
    			n = n.normalize()
    		except Exception:
    			continue  # skip degenerate normals
    
    		# Angle between ray direction and surface normal (0° = normal incidence).
    		# If ray travels along main_direction, normal incidence means n == -ray_dir,
    		# so cos(theta) = - ray_dir · n. [web:36]
    		cos_theta = abs(ray_dir.x * n.x + ray_dir.y * n.y + ray_dir.z * n.z)
    		cos_theta = max(0.0, min(1.0, cos_theta))  # clamp
    		angle_deg = math.degrees(math.acos(cos_theta))
    
    		flux = SOLAR_IRRADIANCE * OBJECT_ABSORPTIVITY * cos_theta
    
                    #flux = absorbed_flux(SOLAR_IRRADIANCE, OBJECT_ABSORPTIVITY, angle_deg)
 
    		# Full data row (including Flux) -> experiment_data.csv
    		writer_exp.writerow([
    			f"{energy:.6f}",
    			f"{x1:.6f}", f"{y1:.6f}", f"{z1:.6f}",
    			f"{nx:.6f}", f"{ny:.6f}", f"{nz:.6f}",
    			f"{wavelength:.6f}",
    			f"{flux:.6f}",
    		])
    
    		# Reduced data row: X, Y, Z, Flux (no header) -> flux_data.csv
    		writer_flux.writerow([
    			f"{x1:.6f}", f"{y1:.6f}", f"{z1:.6f}", f"{flux:.6f}",
    		])
    
    
    print(f"\nExperiment data saved: {len(experiment.points_absorber_Th)} points")
    print(f"Flux data saved: {len(experiment.points_absorber_Th)} points")
    
    # ============================================================================
    # Create 2D Absorption Plots
    # ============================================================================
    
    if PLOT2D:
    	import os
    	import numpy as np
    	import matplotlib
    	matplotlib.use('Agg')   # non-GUI backend, safe in FreeCADCmd
    	import matplotlib.pyplot as plt
    
    	points = getattr(experiment, "points_absorber_Th", None)
    	if not points:
    		print("No absorption points to plot.")
    	else:
    		try:
    			arr = np.asarray(points, dtype=float)
    			xs = arr[:, 1]
    			ys = arr[:, 2]
    		except Exception:
    			xs = [p[1] for p in points if len(p) > 2]
    			ys = [p[2] for p in points if len(p) > 2]
    			xs = np.array(xs, dtype=float)
    			ys = np.array(ys, dtype=float)
    
    		if xs.size == 0:
    			print("No valid absorption coordinates found.")
    		else:
    			plt.figure(figsize=(6, 6))
    			plt.scatter(xs, ys, s=0.5, c='k', marker='.')
    			plt.xlabel("X")
    			plt.ylabel("Y")
    			plt.title(f"Absorption points (N={xs.size})")
    			plt.gca().set_aspect("equal", adjustable="box")
    			plt.tight_layout()
    
    			plot_path = os.path.join(ABSORPTION_PLOT_DIR, f'absorption_plot_{ITER_ID}.png')
    			plt.savefig(plot_path, dpi=300, bbox_inches='tight')  # no plt.show() [web:478][web:479]
    			plt.close()
    			print(f"Plot saved: {plot_path}")
    
    # ============================================================================
    # Log Complexity and Runtime
    # ============================================================================
    
    complexity_log_path = f"{DOCUMENTATION_DIR}/complexity_vs_runtime.csv"
    log_header = not os.path.exists(complexity_log_path)
    with open(complexity_log_path, 'a', newline='') as f_log:
        writer = csv.writer(f_log)
        if log_header:
            writer.writerow(['iter_id', 'num_faces', 'total_complexity_score',
                              'mean_complexity_per_face', 'num_rays', 'elapsed_seconds'])
        writer.writerow([ITER_ID, geometry_complexity['num_faces'],
                          geometry_complexity['total_complexity_score'],
                          geometry_complexity['mean_complexity_per_face'],
                          NUM_RAYS, time.perf_counter() - _start_time])

except Exception as e:
	error_message = str(e)
	print(f"ERROR: Simulation failed: {error_message}")

finally:
    if not KEEP_WORKING_COPY: # Delete working copy if not keeping
        try:
            FreeCAD.closeDocument(doc.Name)
        except Exception:
            pass
        try:
            if os.path.exists(temp_path):
                os.remove(temp_path)
                print(f"Deleted working copy: {temp_path}")
        except OSError as e:
            print(f"WARNING: Could not delete working copy {temp_path}: {e}")
	
    # Write FreeCAD to Abaqus json 
    write_result_json(
        success=success,
        num_faces=num_faces,
        flux_data_path=FLUX_DATA_FILEPATH if success else None,
        error_message=error_message
    )
	
	
### stop timer and report elapsed time
_elapsed = time.perf_counter() - _start_time  # TIMING
print(f"\nTotal script elapsed time: {_elapsed:.3f} seconds")  # TIMING
